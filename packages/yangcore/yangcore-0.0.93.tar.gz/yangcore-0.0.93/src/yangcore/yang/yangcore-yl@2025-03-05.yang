module yangcore-yl {
  yang-version 1.1;
  namespace "https://watsen.net/yangcore-yl";
  prefix yangcore-yl;

  import ietf-yang-types {
    prefix yang;
    reference
      "RFC 6991: Common YANG Data Types";
  }

  import ietf-inet-types {
    prefix inet;
    reference
      "RFC 6991: Common YANG Data Types";
  }

  import ietf-yang-library {
    prefix yl;
    reference
      "RFC 8525: YANG Library";
  }

  organization
    "Watsen Networks (https://watsen.net)";

  description
    "This module deviates the YANG Library data model

     Copyright (c) 2019-2025 Watsen Networks.  All Rights Reserved.";


  revision "2025-03-05" {
    description
      "Initial version";
  }

  // disable legacy YL API and notifications
  deviation /yl:modules-state {
    deviate not-supported;
  }
  deviation /yl:yang-library-change {
    deviate not-supported;
  }
  deviation /yl:yang-library-update {
    deviate not-supported;
  }

} // module
